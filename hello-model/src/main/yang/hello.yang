/*
 * Copyright (c) 2013, project authors and/or its affiliates.
 * All rights reserved.
 *
 * Redistribution and use in source and binary forms, with or without
 * modification, are permitted provided that the following conditions
 * are met:
 *
 *   - Redistributions of source code must retain the above copyright
 *     notice, this list of conditions and the following disclaimer.
 *
 *   - Redistributions in binary form must reproduce the above copyright
 *     notice, this list of conditions and the following disclaimer in the
 *     documentation and/or other materials provided with the distribution.
 *
 *   - Neither the name of the authors or the names of its
 *     contributors may be used to endorse or promote products derived
 *     from this software without specific prior written permission.
 *
 * THIS SOFTWARE IS PROVIDED BY THE COPYRIGHT HOLDERS AND CONTRIBUTORS "AS
 * IS" AND ANY EXPRESS OR IMPLIED WARRANTIES, INCLUDING, BUT NOT LIMITED TO,
 * THE IMPLIED WARRANTIES OF MERCHANTABILITY AND FITNESS FOR A PARTICULAR
 * PURPOSE ARE DISCLAIMED.  IN NO EVENT SHALL THE COPYRIGHT OWNER OR
 * CONTRIBUTORS BE LIABLE FOR ANY DIRECT, INDIRECT, INCIDENTAL, SPECIAL,
 * EXEMPLARY, OR CONSEQUENTIAL DAMAGES (INCLUDING, BUT NOT LIMITED TO,
 * PROCUREMENT OF SUBSTITUTE GOODS OR SERVICES; LOSS OF USE, DATA, OR
 * PROFITS; OR BUSINESS INTERRUPTION) HOWEVER CAUSED AND ON ANY THEORY OF
 * LIABILITY, WHETHER IN CONTRACT, STRICT LIABILITY, OR TORT (INCLUDING
 * NEGLIGENCE OR OTHERWISE) ARISING IN ANY WAY OUT OF THE USE OF THIS
 * SOFTWARE, EVEN IF ADVISED OF THE POSSIBILITY OF SUCH DAMAGE.
 */
 module hello {
    yang-version 1;
    namespace
        "http://controller.opendaylight.company.com/ns/model/hello";
    prefix hello;
    
    import opendaylight-port-types {prefix port;revision-date "2013-09-25";}
    import opendaylight-inventory {prefix inv;revision-date "2013-08-19";}
   
    organization
        "company.com";
    description
        "This is a sample model that will be used within the context of an
         OpenDayLight SDN controller. This model is meant to be an example
         of the capabilities (types, RPCs, and notifications) that can be
         used within an ODL controller context to generate ODL services that
         can be exposed via ODL's RESTful API as well as via ODL's CLI.";
    contact
        "David Bainbridge <davidk.bainbridge@gmail.com>";
    revision "2013-11-13" {
        description
            "Initial revision.";
    }
    
    rpc say-hello {
        description
            "Perform a hello operation on the specified node.";
        input {
            leaf node-id {
                description
                    "The node on which to perform the hello operation.";
                type
                    inv:node-id;
            }
        }
        output {
            leaf node-response {
                description
                    "The response of the hello operation on the node.";
                type
                    string;
            }
        }
    }
    
    grouping hello {
        leaf name {
            description
                "Some arbitrary name.";
            type
                string;
        }
        leaf value {
            description
                "Some arbitrary value.";
            type
                int64;
        }
    }
    
    rpc get-hello {
        description
            "Retrieve a specific hello instance.";
        input {
            leaf hello-id {
                description
                    "The ID of the hello to retrieve.";
                type
                    string;
            }
        }
        output {
            uses hello {
                description
                    "The hello instance.";
            }           
        }
    }
    
    rpc create-hello {
        description
            "Create a new hello instance.";
        input {
            uses hello {
                description
                    "The new hello instance";
            }
        }
        output {
            leaf hello-id {
                description
                    "The ID of the new resource.";
                type
                    string;
            }
        }
    }
    
    rpc update-hello {
        description
            "Update an existing hello instance.";
        input {
            leaf hello-id {
                description
                    "The ID of the hello instance to update.";
                type
                    string;
            }
            container hello {
              uses hello; 
            }
        }
        output {
            leaf status {
                type enumeration {
                    enum ok;
                    enum created;
                    enum conflict;
                    enum bad_request;
                }
            }
            leaf id {
                type
                    string;                
             }
        }
    }
    
    rpc delete-hello {
            description
            "Retrieve a specific hello instance.";
        input {
            leaf hello-id {
                description
                    "The ID of the hello to retrieve.";
                type
                    string;
            }
        }
        output {
            leaf found {
                description
                    "True is the resource existed, else false.";
                type
                    boolean;
            }
        }
    }
    
    notification hello-done {
        description
            "Notification sent when hello operation is complete, regardless
            of the cause of the operation termination, i.e. success or
            failure.";
        leaf status {
            description
                "Indicates the success or failure of the hello operation.";
            type enumeration {
                enum "success" {
                    value 0;
                    description
                        "State indicating that the hello operation was successful.";
                }
                enum "failed" {
                    value 1;
                    description
                        "State indicating that the hello operation failed.";
                }
            }
        }
    }
}
